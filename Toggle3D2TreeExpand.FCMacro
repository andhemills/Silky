#########################################################
# Toggle 3D2TreeExpand
#
# Working in Silk, it can help to enable the setting
# Preferences > General > Selection > Auto switch to the 3D view containing hte selected item
#
# However, it can also be frustrating to have this enabled, since you might not want to lose
# a selection you recently made.
#
# I found going into preferences to toggle the setting a little much work, so I made a macro
# and assigned a button to it, so now with one click, we can configure the setting!
#
# TODO:
# - Implenent second icon to indicate better if feature is enabled or not.
#
#########################################################

import FreeCAD
import FreeCADGui

param = FreeCAD.ParamGet("User parameter:BaseApp/Preferences/TreeView")
new_val = not param.GetBool("SyncSelection")
param.SetBool("SyncSelection", new_val)
