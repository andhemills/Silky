import FreeCAD
import FreeCADGui
import Part
import ArachNURBS as AN
import numpy as np
from scipy.interpolate import BSpline

#
#SilkyMixCurve
#
#

doc = FreeCAD.ActiveDocument

# --- ControlPoly6_Direct class definition ---
class ControlPoly6_Direct:
    def __init__(self, obj, poles):
        latest_version = "0.01"
        obj.addProperty("App::PropertyVectorList", "Poles", "C1 - Inputs", "6 control poles").Poles = poles
        obj.addProperty("App::PropertyFloatList", "Weights", "C1 - Inputs", "Weights").Weights = [1.0, 1.0, 1.0, 1.0, 1.0, 1.0]
        obj.addProperty("App::PropertyBool", "reverse", "C1 - Inputs", "reverse the parameter direction").reverse = False
        obj.addProperty("Part::PropertyGeometryList", "Legs", "C2 - Outputs", "control segments").Legs
        obj.addProperty("App::PropertyString", "object_type", "C3 - Identifiers", "the workbench class used to create this object").object_type = "ControlPoly6_Direct"
        obj.setEditorMode("object_type", 1)
        obj.addProperty("App::PropertyString", "object_version", "C3 - Identifiers", "the class version of this object").object_version = latest_version
        obj.setEditorMode("object_version", 1)
        obj.addProperty("App::PropertyString", "internalName", "C3 - Identifiers", "the permanent internal FreeCAD name for this object").internalName = obj.Name
        obj.setEditorMode("internalName", 1)
        obj.Proxy = self

    def onDocumentRestored(self, obj):
        obj.recompute()

    def onChanged(self, fp, prop):
        if prop == "reverse":
            fp.recompute()

    def execute(self, fp):
        if 'Restore' in fp.State:
            return
        poles = fp.Poles
        if fp.reverse:
            poles = list(reversed(poles))
        Leg0 = Part.LineSegment(poles[0], poles[1])
        Leg1 = Part.LineSegment(poles[1], poles[2])
        Leg2 = Part.LineSegment(poles[2], poles[3])
        Leg3 = Part.LineSegment(poles[3], poles[4])
        Leg4 = Part.LineSegment(poles[4], poles[5])
        fp.Legs = [Leg0, Leg1, Leg2, Leg3, Leg4]
        fp.Shape = Part.Shape(fp.Legs)

# --- Get selected MixedCurve ---
sel = FreeCADGui.Selection.getSelection()
if len(sel) != 1:
    raise Exception("Please select exactly one MixedCurve object")

mc = sel[0]

# Basic validation
if not hasattr(mc, 'Shape') or len(mc.Shape.Edges) == 0:
    raise Exception(f"{mc.Label} has no shape edges - is it a valid MixedCurve?")

if not hasattr(mc, 'Shape1') or not hasattr(mc, 'Shape2'):
    raise Exception(f"{mc.Label} does not have Shape1/Shape2 - is it a MixedCurve?")

print(f"Processing: {mc.Label}")

# --- Sample MixedCurve directly ---
edge = mc.Shape.Edges[0]
curve = edge.Curve
p0_mc, p1_mc = edge.ParameterRange

# Dense parameter sampling
n_samples = 300  # Increased sample count for enhanced accuracy
t_steps = np.linspace(0, 1, n_samples)

# IMPROVEMENT: Map parameter valuation exactly to the native FreeCAD timeline 
# instead of an independent, raw geometric chord length.
native_params = p0_mc + t_steps * (p1_mc - p0_mc)

Q = np.array([[curve.value(p)[0], curve.value(p)[1], curve.value(p)[2]]
               for p in native_params])

# Exact native endpoints
P0 = Q[0]
P5 = Q[-1]

# --- Target knot vector for 6 control points degree 3 ---
degree = 3
num_ctrl = 6
target_knots = np.array([0, 0, 0, 0, 1/3, 2/3, 1, 1, 1, 1], dtype=float)

# --- Build basis matrix matching the native timeline ---
N = np.zeros((n_samples, num_ctrl))
for i in range(num_ctrl):
    unit = np.zeros(num_ctrl)
    unit[i] = 1.0
    # Evaluating basis matrix mapping cleanly over our uniform t_steps [0 to 1]
    N[:, i] = BSpline(target_knots, unit, degree)(t_steps)

# --- Constrained least squares with fixed endpoints ---
RHS = Q - np.outer(N[:, 0], P0) - np.outer(N[:, -1], P5)
N_mid = N[:, 1:-1]
P_mid, _, _, _ = np.linalg.lstsq(N_mid, RHS, rcond=None)

# --- Assemble final poles ---
final_poles = np.zeros((num_ctrl, 3))
final_poles[0] = P0
final_poles[1:-1] = P_mid
final_poles[-1] = P5

poles_final = [FreeCAD.Vector(float(p[0]), float(p[1]), float(p[2]))
               for p in final_poles]

# --- Measure fit quality ---
fitted_spline = BSpline(target_knots, final_poles, degree)
fitted_pts = fitted_spline(t_steps)
deviations = np.linalg.norm(Q - fitted_pts, axis=1)

print(f"\nFit vs MixedCurve (Native parametric alignment):")
print(f"  avg error: {np.mean(deviations):.6f}")
print(f"  max error: {np.max(deviations):.6f}")

print(f"\nFinal 6 poles:")
for i, p in enumerate(poles_final):
    print(f"  P{i+1}: {p}")

# --- Create ControlPoly6_Direct ---
cp6 = doc.addObject("Part::FeaturePython", "ControlPoly6_Direct_000")
ControlPoly6_Direct(cp6, poles_final)
cp6.ViewObject.Proxy = 0
cp6.ViewObject.LineWidth = 1.00
cp6.ViewObject.LineColor = (0.00, 1.00, 1.00)
cp6.ViewObject.PointSize = 4.00
cp6.ViewObject.PointColor = (0.00, 0.00, 1.00)
doc.recompute()
print(f"ControlPoly6_Direct created: {cp6.Label}")

# --- Create CubicCurve_6 ---
cc6 = doc.addObject("Part::FeaturePython", "CubicCurve_6_Direct_000")
AN.CubicCurve_6(cc6, cp6)
cc6.ViewObject.Proxy = 0
cc6.ViewObject.LineWidth = 2.00
cc6.ViewObject.LineColor = (1.00, 0.50, 0.00)
doc.recompute()
print(f"CubicCurve_6 created: {cc6.Label}")
print("Done.")
